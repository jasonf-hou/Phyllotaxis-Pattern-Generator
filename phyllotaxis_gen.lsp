(setq low 1)
(setq num_pts (getint "\nSpecify number of pillars: "))
(setq center (getpoint "\nSpecify center point: "))
(setq p_radius 70) ;(getint "\nSpecify radius of pillars: "))
;(setq prad_grad (getint "\nSpecify radius of pillars: "))
(setq base (getreal "\nSpecify phylo base mult: "))
(setq base_r (getint "\nSpecify base separation distance: "))
;(setq grad (getint "\nSpecify linear gradient delta: "))
;(setq prad_grad (getint"\nSpecify pillar radius gradient: "))
(setq base_angle (* (* pi (+ 1 (sqrt 5))) base))
(setq rad_grad 0)
(while (<= low num_pts)
  (setq r (sqrt (* low base_r)))
  (setq theta (* low base_angle))
  ;(setq rad_grad (+ rad_grad (rem theta (* 2 pi))))
  ;(princ (* (/ 180 pi) rad_grad))
  ;(if (>= rad_grad (* 2 pi)) (setq p_radius (+ p_radius prad_grad)) (setq rad_grad 0))
  (setq p_radius (* p_radius (/ (- (* 1.5 r) 1) (* 1.5c r))))
  ;(princ p_radius)
  (setq x (* r (cos theta)))
  (setq y (* r (sin theta)))
  (setq draw_pt (list (+ x (nth 0 center)) (+ y (nth 1 center))))
  ; draw circle, enforce design constraints
  (command "circle" draw_pt p_radius)
  (setq low (+ low 1))
  ; (if (= (/ theta (* 2 pi)) 0) (setq prad_grad (- prad_grad 10)))
)
